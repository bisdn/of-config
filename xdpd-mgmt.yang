module xdpd-mgmt {
  namespace "urn:xdpd:mgmt:yang";
  prefix xdpd-mgmt;

  import of-config1.1.1  { prefix ofc; }

  organization "BISDN GmbH";

  contact "info@bisdn.de";

  description "";

  revision 2014-10-01 {
    description "First Draft";
    reference "nn";
  }

  augment "/ofc:capable-switch" {
    container cross-connections {
      description "";
      presence "";
      
      list cross-connection {
        description "";
        key "name";
        
        leaf name {
          type string;
        }

        list switch {
          description "";
          key "id";
          min-elements 2;
          max-elements 2;
          
          leaf id {
            type leafref {
              path "/ofc:capable-switch/ofc:logical-switches/ofc:switch/ofc:id";
            }
          }
          
          leaf requested-of-port-number {
            type uint64 {
              range "1..512";
            }
          }

          leaf of-port-number {
            type uint64;
            config false;
          }

          leaf portname {
            config false;
            type string;
          }
        }
      }
    }
  }
}
